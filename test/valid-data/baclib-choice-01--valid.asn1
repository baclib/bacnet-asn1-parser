BAClibTimeStamp ::= CHOICE {
    time [0] BAClibTime,                    -- Simple time value
    sequence-number [1] INTEGER,            -- Sequence counter
    date-time [2] BAClibDateTime            -- Full date and time
} -- Timestamp can be represented in multiple ways
