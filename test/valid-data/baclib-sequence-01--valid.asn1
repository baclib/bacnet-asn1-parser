BAClibObjectIdentifier ::= SEQUENCE {
    object-type BAClibObjectType,           -- Type of BACnet object
    instance-number INTEGER                 -- Unique instance within type
} -- BACnet object identifier structure
